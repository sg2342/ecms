CMSECCAlgs-2009-88
  { iso(1) member-body(2) us(840) rsadsi(113549) pkcs(1) pkcs-9(9)
    smime(16) modules(0) id-mod-cms-ecc-alg-2009-88(45) }

DEFINITIONS IMPLICIT TAGS ::=

BEGIN

-- EXPORTS ALL

IMPORTS

-- From [PKI]

AlgorithmIdentifier
  FROM PKIX1Explicit88
    { iso(1) identified-organization(3) dod(6)
      internet(1) security(5) mechanisms(5) pkix(7) mod(0)
      pkix1-explicit(18) }

-- From [RSAOAEP]

id-sha224, id-sha256, id-sha384, id-sha512
  FROM PKIX1-PSS-OAEP-Algorithms
    { iso(1) identified-organization(3) dod(6) internet(1)
      security(5) mechanisms(5) pkix(7) id-mod(0)
      id-mod-pkix1-rsa-pkalgs(33) }

-- From [PKI-ALG]

id-sha1, ecdsa-with-SHA1, ecdsa-with-SHA224,
ecdsa-with-SHA256, ecdsa-with-SHA384, ecdsa-with-SHA512,
id-ecPublicKey, ECDSA-Sig-Value, ECPoint, ECParameters
  FROM PKIX1Algorithms2008
    { iso(1) identified-organization(3) dod(6) internet(1)
      security(5) mechanisms(5) pkix(7) id-mod(0) 45 }

-- From [CMS]

OriginatorPublicKey, UserKeyingMaterial
  FROM CryptographicMessageSyntax2004
    { iso(1) member-body(2) us(840) rsadsi(113549) pkcs(1) pkcs-9(9)
      smime(16) modules(0) cms-2004(24) }

-- From [CMS-ALG]

hMAC-SHA1, des-ede3-cbc, id-alg-CMS3DESwrap, CBCParameter
  FROM CryptographicMessageSyntaxAlgorithms
    { iso(1) member-body(2) us(840) rsadsi(113549) pkcs(1) pkcs-9(9)
      smime(16) modules(0) cmsalg-2001(16) }

-- From [CMS-AES]

id-aes128-CBC, id-aes192-CBC, id-aes256-CBC, AES-IV,
id-aes128-wrap, id-aes192-wrap, id-aes256-wrap
  FROM CMSAesRsaesOaep
    { iso(1) member-body(2) us(840) rsadsi(113549) pkcs(1) pkcs-9(9)
      smime(16) modules(0) id-mod-cms-aes(19) }

-- From [CMS-AESCG]

id-aes128-CCM, id-aes192-CCM, id-aes256-CCM, CCMParameters,
id-aes128-GCM, id-aes192-GCM, id-aes256-GCM, GCMParameters
  FROM CMS-AES-CCM-and-AES-GCM
    { iso(1) member-body(2) us(840) rsadsi(113549) pkcs(1) pkcs-9(9)
      smime(16) modules(0) id-mod-cms-aes(32) }

;

--
-- Message Digest Algorithms: Imported from [PKI-ALG] and [RSAOAEP]
--

-- id-sha1 Parameters are preferred absent
-- id-sha224 Parameters are preferred absent
-- id-sha256 Parameters are preferred absent
-- id-sha384 Parameters are preferred absent
-- id-sha512 Parameters are preferred absent

--
-- Signature Algorithms: Imported from [PKI-ALG]
--

-- ecdsa-with-SHA1 Parameters are NULL
-- ecdsa-with-SHA224 Parameters are absent
-- ecdsa-with-SHA256 Parameters are absent
-- ecdsa-with-SHA384 Parameters are absent
-- ecdsa-with-SHA512 Parameters are absent

-- ECDSA Signature Value
-- Contents of SignatureValue OCTET STRING

-- ECDSA-Sig-Value ::= SEQUENCE {
--   r  INTEGER,
--   s  INTEGER
-- }

--
-- Key Agreement Algorithms
--

x9-63-scheme OBJECT IDENTIFIER ::= {
  iso(1) identified-organization(3) tc68(133) country(16) x9(840)
  x9-63(63) schemes(0) }
secg-scheme OBJECT IDENTIFIER ::= {
  iso(1) identified-organization(3) certicom(132) schemes(1) }

--
-- Diffie-Hellman Single Pass, Standard, with KDFs
--

-- Parameters are always present and indicate the key wrap algorithm
-- with KeyWrapAlgorithm.

dhSinglePass-stdDH-sha1kdf-scheme OBJECT IDENTIFIER ::= {
  x9-63-scheme 2 }

dhSinglePass-stdDH-sha224kdf-scheme OBJECT IDENTIFIER ::= {
  secg-scheme 11 0 }

dhSinglePass-stdDH-sha256kdf-scheme OBJECT IDENTIFIER ::= {
  secg-scheme 11 1 }

dhSinglePass-stdDH-sha384kdf-scheme OBJECT IDENTIFIER ::= {
  secg-scheme 11 2 }

dhSinglePass-stdDH-sha512kdf-scheme OBJECT IDENTIFIER ::= {
  secg-scheme 11 3 }

--
-- Diffie-Hellman Single Pass, Cofactor, with KDFs
--

dhSinglePass-cofactorDH-sha1kdf-scheme OBJECT IDENTIFIER ::= {
  x9-63-scheme 3 }

dhSinglePass-cofactorDH-sha224kdf-scheme OBJECT IDENTIFIER ::= {
  secg-scheme 14 0 }

dhSinglePass-cofactorDH-sha256kdf-scheme OBJECT IDENTIFIER ::= {
  secg-scheme 14 1 }

dhSinglePass-cofactorDH-sha384kdf-scheme OBJECT IDENTIFIER ::= {
  secg-scheme 14 2 }

dhSinglePass-cofactorDH-sha512kdf-scheme OBJECT IDENTIFIER ::= {
  secg-scheme 14 3 }

--
-- MQV Single Pass, Cofactor, with KDFs
--

mqvSinglePass-sha1kdf-scheme OBJECT IDENTIFIER ::= {
  x9-63-scheme 16 }

mqvSinglePass-sha224kdf-scheme OBJECT IDENTIFIER ::= {
  secg-scheme 15 0 }

mqvSinglePass-sha256kdf-scheme OBJECT IDENTIFIER ::= {
  secg-scheme 15 1 }

mqvSinglePass-sha384kdf-scheme OBJECT IDENTIFIER ::= {
  secg-scheme 15 2 }

mqvSinglePass-sha512kdf-scheme OBJECT IDENTIFIER ::= {
  secg-scheme 15 3 }

--
-- Key Wrap Algorithms: Imported from [CMS-ALG] and [CMS-AES]
--

KeyWrapAlgorithm ::= AlgorithmIdentifier

-- id-alg-CMS3DESwrap Parameters are NULL
-- id-aes128-wrap Parameters are absent
-- id-aes192-wrap Parameters are absent
-- id-aes256-wrap Parameters are absent

--
-- Content Encryption Algorithms: Imported from [CMS-ALG]
-- and [CMS-AES]
--

-- des-ede3-cbc Parameters are CBCParameter
-- id-aes128-CBC Parameters are AES-IV
-- id-aes192-CBC Parameters are AES-IV
-- id-aes256-CBC Parameters are AES-IV
-- id-aes128-CCM Parameters are CCMParameters
-- id-aes192-CCM Parameters are CCMParameters
-- id-aes256-CCM Parameters are CCMParameters
-- id-aes128-GCM Parameters are GCMParameters
-- id-aes192-GCM Parameters are GCMParameters
-- id-aes256-GCM Parameters are GCMParameters

--
-- Message Authentication Code Algorithms
--

-- hMAC-SHA1 Parameters are preferred absent

-- HMAC with SHA-224, SHA-256, SHA_384, and SHA-512 Parameters are
-- absent

id-hmacWithSHA224 OBJECT IDENTIFIER ::= {
  iso(1) member-body(2) us(840) rsadsi(113549)
  digestAlgorithm(2) 8 }

id-hmacWithSHA256 OBJECT IDENTIFIER ::= {
  iso(1) member-body(2) us(840) rsadsi(113549)
  digestAlgorithm(2) 9 }

id-hmacWithSHA384 OBJECT IDENTIFIER ::= {
  iso(1) member-body(2) us(840) rsadsi(113549)
  digestAlgorithm(2) 10 }

id-hmacWithSHA512 OBJECT IDENTIFIER ::= {
  iso(1) member-body(2) us(840) rsadsi(113549)
  digestAlgorithm(2) 11 }


--
-- Originator Public Key Algorithms: Imported from [PKI-ALG]
--

-- id-ecPublicKey Parameters are absent, NULL, or ECParameters

-- Format for both ephemeral and static public keys: Imported from
-- [PKI-ALG]

-- ECPoint ::= OCTET STRING

-- ECParameters ::= CHOICE {
--   namedCurve      OBJECT IDENTIFIER
--   commented out in [PKI-ALG]  implicitCurve   NULL
--   commented out in [PKI-ALG]  specifiedCurve  SpecifiedECDomain
--   commented out in [PKI-ALG]  ...
-- }
    -- implicitCurve and specifiedCurve MUST NOT be used in PKIX.
    -- Details for SpecifiedECDomain can be found in [X9.62].
    -- Any future additions to this CHOICE should be coordinated
    -- with ANSI X9.

-- Format of KeyAgreeRecipientInfo ukm field when used with
-- ECMQV

MQVuserKeyingMaterial ::= SEQUENCE {
  ephemeralPublicKey       OriginatorPublicKey,
  addedukm             [0] EXPLICIT UserKeyingMaterial OPTIONAL
}

-- 'SharedInfo' for input to KDF when using ECDH and ECMQV with
-- EnvelopedData, AuthenticatedData, or AuthEnvelopedData

ECC-CMS-SharedInfo ::= SEQUENCE {
  keyInfo         AlgorithmIdentifier,
  entityUInfo [0] EXPLICIT OCTET STRING OPTIONAL,
  suppPubInfo [2] EXPLICIT OCTET STRING
}

--
-- S/MIME Capabilities
-- An identifier followed by type.
--


--
-- S/MIME Capabilities: Message Digest Algorithms
--

-- Found in [CMS-SHA2].

--
-- S/MIME Capabilities: Signature Algorithms
--

-- ecdsa-with-SHA1 Type NULL
-- ecdsa-with-SHA224 Type absent
-- ecdsa-with-SHA256 Type absent
-- ecdsa-with-SHA384 Type absent
-- ecdsa-with-SHA512 Type absent

--
-- S/MIME Capabilities: ECDH, Single Pass, Standard
--

-- dhSinglePass-stdDH-sha1kdf Type is the KeyWrapAlgorithm
-- dhSinglePass-stdDH-sha224kdf Type is the KeyWrapAlgorithm
-- dhSinglePass-stdDH-sha256kdf Type is the KeyWrapAlgorithm
-- dhSinglePass-stdDH-sha384kdf Type is the KeyWrapAlgorithm
-- dhSinglePass-stdDH-sha512kdf Type is the KeyWrapAlgorithm


--
-- S/MIME Capabilities: ECDH, Single Pass, Cofactor
--

-- dhSinglePass-cofactorDH-sha1kdf Type is the KeyWrapAlgorithm
-- dhSinglePass-cofactorDH-sha224kdf Type is the KeyWrapAlgorithm
-- dhSinglePass-cofactorDH-sha256kdf Type is the KeyWrapAlgorithm
-- dhSinglePass-cofactorDH-sha384kdf Type is the KeyWrapAlgorithm
-- dhSinglePass-cofactorDH-sha512kdf Type is the KeyWrapAlgorithm

--
-- S/MIME Capabilities: ECMQV, Single Pass, Standard
--

-- mqvSinglePass-sha1kdf Type is the KeyWrapAlgorithm
-- mqvSinglePass-sha224kdf Type is the KeyWrapAlgorithm
-- mqvSinglePass-sha256kdf Type is the KeyWrapAlgorithm
-- mqvSinglePass-sha384kdf Type is the KeyWrapAlgorithm
-- mqvSinglePass-sha512kdf Type is the KeyWrapAlgorithm


--
-- S/MIME Capabilities: Message Authentication Code Algorithms
--

-- hMACSHA1 Type is preferred absent
-- id-hmacWithSHA224 Type is absent
-- if-hmacWithSHA256 Type is absent
-- id-hmacWithSHA384 Type is absent
-- id-hmacWithSHA512 Type is absent

END
